# SysMLmodel
generated by Papyrus Requirement from exportSpecRealtions.uml

# Specification: specif

## req100: Req_0 (ReqType4)
- RelationType0 -> req110

## req200: Req_7 (ReqType3)
- Attribute1: 0
- RelationType1 -> req130
- RelationType3 -> req500
- RelationType3 -> req600
- RelationType3 -> req600

## req300: Req_9 (ReqType2)
- Attribute1: false
- RelationType1 -> req100
- RelationType1 -> req140

## req400: Req_11 (ReqType2)
- Attribute1: false
- RelationType1 -> req100

## req500: Req_13 (ReqType1)
- Attribute1: 0.0

## req600: Req_14 (ReqType0)
- Attribute1: Low
- Attribute2: Idea

## req110: Req_1 (ReqType4)

## req120: Req_2 (ReqType1)
- Attribute1: 0.0

## req130: Req_3 (ReqType0)
- Attribute1: Low
- Attribute2: Idea

## req140: Req_4 (ReqType0)
- Attribute1: Low
- Attribute2: Idea

## req150: Req_5 (ReqType0)
- Attribute1: Low
- Attribute2: Idea

## req160: Req_6 (ReqType0)
- Attribute1: Low
- Attribute2: Idea

## req210: Req_8 (ReqType4)

## req310: Req_10 (ReqType3)
- Attribute1: 0

## req410: Req_12 (ReqType4)
